// Copyright (c) 2026 STAVROPOULOS LAW. All Rights Reserved.
//
// GRAIL — Policy. Every adjustable limit lives here and nowhere else (Δ-12ε).
//
// The Constitution holds what is ALWAYS TRUE of the mechanism. This package holds what is
// PERMITTED RIGHT NOW: by whom, with which key, within which envelope. Nothing here may cause a
// telos to fail. A limit that can veto an aim is not a limit, it is a lowered aim — which is how
// the cost ceiling first arrived inside T7 and why it was taken out again.
//
// Written, not machine-checked here.

package GRAIL_Policy {
	private import ScalarValues::*;

	// Α-15. The envelope narrows WHAT IS ATTEMPTED — scope, breadth, how many matters run in
	// parallel. It never lowers the class of proof, and it never turns a met telos into a failed
	// one. Fail-closed: when the budget is exhausted the work stops and says so, rather than
	// continuing with weaker evidence.
	part def CostAndTimeEnvelope {
		attribute costCeiling : Real;
		attribute timeCeiling : Real;
		attribute reducesScope : Boolean = true;
		attribute reducesProofClass : Boolean = false;
		attribute canCauseTelosFailure : Boolean = false;
	}

	// Α-12. The system never produces a probability of the outcome of a case. This is a
	// prohibition, not a capability, so it is policy and not telos — and being policy does not
	// make it weak: it is enforced at the mediated point, where the effect would leave.
	part def NoOutcomeProbability {
		attribute outcomeProbabilityEverProduced : Boolean = false;
	}

	// Δ-12(β). Policy binds only what the core mediates. Zero ambient authority is the property
	// that makes everything in this package real rather than advisory, and it is stated in T9 as
	// a capability of the mechanism — not here, because it is not adjustable.
	part def PolicyDecisionPoint {
		attribute changeTakesEffectWithoutRebuild : Boolean = true;
		attribute changeTakesEffectWithoutRestart : Boolean = true;
	}

	// --------------------------------------------------------------- the one decision point
	// Δ-12(α): the core knows nothing about what is forbidden. It knows only that every effect
	// passes through a permission. Every rule that DECIDES lives here, is read as data, and
	// changes without redesign, rebuild or restart. There is no second check inside the kernel to
	// overrule this one — a core that carries its own rule is a limit baked into the mechanism,
	// which is what Δ-12 exists to remove.

	part def PolicyDecisionSeat {
		attribute rulesInsideCore : Integer = 0;
		attribute rulesReadAsData : Boolean = true;
		attribute changeWithoutRebuild : Boolean = true;

		assert constraint { rulesInsideCore == 0 }
		assert constraint { rulesReadAsData == true }
	}

	// Autonomy. The five conditions of the epistemic contract, applied here and not in the kernel.
	part def AutonomyRule {
		attribute thetaSafe : Real;
		attribute requireFullyReversible : Boolean = true;
		attribute requireCourtVerdict : Boolean = true;
		attribute requireNoInvariantViolation : Boolean = true;
		attribute requireRootUntouched : Boolean = true;
		// Policy default, the creator's to change: an act whose reversibility is not proven counts
		// as irreversible, and the inverse is staged before the act.
		attribute unprovenReversibilityCountsAsIrreversible : Boolean = true;
		attribute inverseMustBePreStaged : Boolean = true;
	}

	// Reach. Where authorization exists, the scanner is admitted at full strength. The bound is
	// unauthorized access to third-party systems — source: law on unlawful access to information
	// systems; scope: systems the Principal holds no authorization for, and nothing else (article
	// 9: the bound does not spread). It is evaluated HERE, as data, and opens the moment the
	// authorization record exists.
	part def ReachRule {
		attribute authorizationOnRecord : Boolean;
		attribute admitsAtFullStrength : Boolean = true;
		attribute secondCheckInsideCore : Boolean = false;

		assert constraint { secondCheckInsideCore == false }
	}

	// Crossing a policy boundary. Also a decision, also here.
	part def CrossingRule {
		attribute requireAdversaryProof : Boolean = true;
		attribute requireCostOfCrossingLower : Boolean = true;
		attribute grantExpires : Boolean = true;
	}

	part def Sentinel;
}
